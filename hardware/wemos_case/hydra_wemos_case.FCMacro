# -*- coding: utf-8 -*-
"""Hydra Web case — a box for a Wemos D1 mini Pro + MAX3232 module on the back of a
Fluke Hydra 2620A/2625A.

The box covers the unused IEEE-488 (GPIB) opening, is screwed through the two GPIB
mounting holes, and the MAX3232's DB9 female plugs straight into the Hydra's RS-232 port
just above it: no external cable.

Run it
  * in FreeCAD:  Macro → Macros… → select this file → Execute
                 (builds "Body" and "Lid" in a new document; edit the numbers below and run again)
  * from a shell with CadQuery (pip install cadquery):
                 python3 hydra_wemos_case.FCMacro      -> writes STEP and STL next to this file

Coordinates (mm): origin at the centre of the RS-232 DB9 on the panel surface,
+Y towards the terminal block (up the panel), +X towards the option slot, +Z out of the panel.

https://github.com/metallarox/fluke_hydra_monitor  ·  IV3HGA
"""

# =====================================================================================
# PARAMETERS — measure the ones marked (*) with a caliper before printing
# =====================================================================================
P = dict(
    # --- panel datums ---------------------------------------------------------------
    db9_screw_pitch=25.0,     # DB9 hex-standoff spacing (standard 24.99)
    db9_to_gpib=12.0,         # (*) lower DB9 standoff centre -> upper GPIB hole centre
    gpib_pitch=47.04,         # (*) GPIB hole spacing (IEEE-488 24-pin standard 47.04)
    gpib_dx=0.0,              # (*) lateral offset of the GPIB holes from the DB9 axis
    gpib_hole_d=3.4,          # clearance hole for M3 in the box
    # fixing: two M3 countersunk screws from inside the box through the GPIB holes.
    # With a nut behind the panel (instrument opened once) they clamp; without nuts
    # they still locate the box while the MAX3232's DB9 screws hold it.
    key=False,                # locating key into the GPIB cut-out (needs support when printing)
    key_len=30.0, key_w=8.5, key_h=1.2,
    # --- box ------------------------------------------------------------------------
    x_left=-16.0,             # (*) outer side towards the "9 8 7 6" print
    x_right=15.0,             # (*) outer side towards the option slot
    y_top=15.5,               # (*) top end: flush with the DB9 flange (terminal block right above!)
    y_bottom_margin=9.0,      # below the lower GPIB hole
    depth=42.0,               # total, lid included (MAX3232 board sticks out ~35 mm)
    wall=1.8,
    back=3.0,                 # back plate thickness
    lid=2.4,                  # lid thickness
    top_open=True,            # no top wall: the terminal block sits right above the DB9
    db9_window_w=16.0,        # opening in the back plate around the Hydra DB9 (X)
    db9_window_y0=-17.0,      # ...from this Y upwards
    corner_r=2.5,             # vertical edges rounding
    # --- Wemos D1 mini Pro cradle ---------------------------------------------------
    wemos_l=34.2, wemos_w=25.6, wemos_t=1.0,
    wemos_y_top=-31.8,        # Y of the antenna end (USB end points down)
    wemos_lift=6.0,           # board bottom above the back plate (room for parts below)
    cradle_wall=1.6, cradle_rim=1.0, cradle_clear=0.25,
    usb_w=13.0, usb_z0=3.4, usb_z1=16.5,   # opening in the bottom wall
    # --- lid screws -----------------------------------------------------------------
    boss_d=6.5, boss_hole_d=2.5,           # M3 self-tapping into the bosses
    lid_hole_d=3.4,
    boss_top_y=-20.0, boss_bottom_inset=3.0,
    # --- lid decoration -------------------------------------------------------------
    vents=True, vent_w=2.0, vent_len=16.0, vent_pitch=4.0,
    text_main="HYDRA WiFi", text_call="IV3HGA", text_depth=0.6,
)


# =====================================================================================
# geometry backends: FreeCAD (Part) or CadQuery — same OpenCascade kernel
# =====================================================================================
try:
    import FreeCAD as App
    import Part
    BACKEND = 'freecad'
except ImportError:
    import cadquery as cq
    BACKEND = 'cadquery'

import math


def box(x0, y0, z0, x1, y1, z1):
    x0, x1 = min(x0, x1), max(x0, x1)
    y0, y1 = min(y0, y1), max(y0, y1)
    z0, z1 = min(z0, z1), max(z0, z1)
    if BACKEND == 'freecad':
        return Part.makeBox(x1 - x0, y1 - y0, z1 - z0, App.Vector(x0, y0, z0))
    return cq.Solid.makeBox(x1 - x0, y1 - y0, z1 - z0, pnt=cq.Vector(x0, y0, z0))


def cyl(x, y, z0, z1, d):
    if BACKEND == 'freecad':
        return Part.makeCylinder(d / 2, z1 - z0, App.Vector(x, y, z0), App.Vector(0, 0, 1))
    return cq.Solid.makeCylinder(d / 2, z1 - z0, pnt=cq.Vector(x, y, z0), dir=cq.Vector(0, 0, 1))


def cone(x, y, z0, z1, d0, d1):
    if BACKEND == 'freecad':
        return Part.makeCone(d0 / 2, d1 / 2, z1 - z0, App.Vector(x, y, z0), App.Vector(0, 0, 1))
    return cq.Solid.makeCone(d0 / 2, d1 / 2, z1 - z0, pnt=cq.Vector(x, y, z0), dir=cq.Vector(0, 0, 1))


def rbox(x0, y0, z0, x1, y1, z1, r):
    """Box with rounded vertical edges."""
    x0, x1 = min(x0, x1), max(x0, x1)
    y0, y1 = min(y0, y1), max(y0, y1)
    r = min(r, (x1 - x0) / 2 - 1e-3, (y1 - y0) / 2 - 1e-3)
    if r <= 0.01:
        return box(x0, y0, z0, x1, y1, z1)
    s = union([box(x0 + r, y0, z0, x1 - r, y1, z1), box(x0, y0 + r, z0, x1, y1 - r, z1)] +
              [cyl(cx, cy, z0, z1, 2 * r) for cx in (x0 + r, x1 - r) for cy in (y0 + r, y1 - r)])
    return s


def union(shapes):
    s = shapes[0]
    for t in shapes[1:]:
        s = s.fuse(t)
    return clean(s)


def cut(s, tools):
    for t in tools:
        s = s.cut(t)
    return clean(s)


def clean(s):
    if BACKEND == 'freecad':
        try:
            return s.removeSplitter()
        except Exception:
            return s
    return s.clean()


def text_solid(txt, size, x, y, z0, h, rot90=True):
    """Extruded text centred at (x, y), reading along Y when rot90. None if unavailable."""
    if not txt:
        return None
    if BACKEND == 'cadquery':
        wp = cq.Workplane('XY').workplane(offset=z0)
        t = wp.text(txt, size, h, combine=False, halign='center', valign='center', font='Sans')
        solid = t.val()
        if rot90:
            solid = solid.rotate(cq.Vector(0, 0, 0), cq.Vector(0, 0, 1), 90)
        return solid.translate(cq.Vector(x, y, 0))
    # FreeCAD: Part.makeWireString needs a TTF; try a few common ones
    import os
    fonts = ['/usr/share/fonts/truetype/dejavu/DejaVuSans-Bold.ttf',
             '/usr/share/fonts/TTF/DejaVuSans-Bold.ttf',
             'C:/Windows/Fonts/arialbd.ttf', '/Library/Fonts/Arial Bold.ttf',
             '/System/Library/Fonts/Supplemental/Arial Bold.ttf']
    font = next((f for f in fonts if os.path.exists(f)), None)
    if font is None:
        return None
    try:
        wires = Part.makeWireString(txt, font, size, 0)
        faces = [Part.makeFace(char, 'Part::FaceMakerBullseye') for char in wires if char]
        comp = Part.Compound(faces)
        bb = comp.BoundBox
        comp.translate(App.Vector(-bb.Center.x, -bb.Center.y, z0))
        sol = comp.extrude(App.Vector(0, 0, h))
        if rot90:
            sol.rotate(App.Vector(0, 0, 0), App.Vector(0, 0, 1), 90)
        sol.translate(App.Vector(x, y, 0))
        return sol
    except Exception:
        return None


# =====================================================================================
# model
# =====================================================================================
def derived(p):
    d = dict(p)
    d['db9_lo'] = -p['db9_screw_pitch'] / 2
    d['gpib_y1'] = d['db9_lo'] - p['db9_to_gpib']           # upper GPIB hole
    d['gpib_y2'] = d['gpib_y1'] - p['gpib_pitch']           # lower GPIB hole
    d['gpib_yc'] = (d['gpib_y1'] + d['gpib_y2']) / 2
    d['y_bottom'] = d['gpib_y2'] - p['y_bottom_margin']
    d['body_top'] = p['depth'] - p['lid']                   # Z of the lid seat
    d['xc'] = (p['x_left'] + p['x_right']) / 2
    d['ix0'], d['ix1'] = p['x_left'] + p['wall'], p['x_right'] - p['wall']
    d['iy0'] = d['y_bottom'] + p['wall']
    d['wemos_y0'] = p['wemos_y_top'] - p['wemos_l']
    d['board_z'] = p['back'] + p['wemos_lift']
    r = p['boss_d'] / 2
    d['bosses'] = [(d['ix0'] + r, p['boss_top_y']), (d['ix1'] - r, p['boss_top_y']),
                   (d['ix0'] + r, d['iy0'] + p['boss_bottom_inset']),
                   (d['ix1'] - r, d['iy0'] + p['boss_bottom_inset'])]
    return d


def make_body(p):
    d = derived(p)
    xl, xr, yb, yt = p['x_left'], p['x_right'], d['y_bottom'], p['y_top']
    zt, w = d['body_top'], p['wall']

    outer = rbox(xl, yb, 0, xr, yt, zt, p['corner_r'])
    inner_top = yt + 1 if p['top_open'] else yt - w
    inner = rbox(d['ix0'], d['iy0'], p['back'], d['ix1'], inner_top, zt + 1, max(0.4, p['corner_r'] - w))
    body = cut(outer, [inner])

    # window around the Hydra DB9 (shell + hex standoffs), open towards the top
    body = cut(body, [box(-p['db9_window_w'] / 2, p['db9_window_y0'], -1, p['db9_window_w'] / 2, yt + 1, p['back'] + 0.01)])

    # lid screw bosses
    adds = [cyl(x, y, p['back'] - 0.01, zt, p['boss_d']) for x, y in d['bosses']]

    # Wemos cradle: frame with a rim under the board edges
    cw, rim, cl = p['cradle_wall'], p['cradle_rim'], p['cradle_clear']
    bx0, bx1 = d['xc'] - p['wemos_w'] / 2 - cl, d['xc'] + p['wemos_w'] / 2 + cl
    by0, by1 = d['wemos_y0'] - cl, p['wemos_y_top'] + cl
    zb = d['board_z']
    frame_top = zb + p['wemos_t'] + 2.0
    frame = rbox(bx0 - cw, by0 - cw, p['back'] - 0.01, bx1 + cw, by1 + cw, frame_top, 1.0)
    frame = cut(frame, [box(bx0, by0, zb, bx1, by1, frame_top + 1),                 # board pocket
                        box(bx0 + rim, by0 + rim, p['back'], bx1 - rim, by1 - rim, zb + 0.01),  # under board
                        box(d['xc'] - p['usb_w'] / 2, by0 - cw - 1, p['back'], d['xc'] + p['usb_w'] / 2, by0 + 1, frame_top + 1),
                        box(bx0 + 4, by1 - 1, zb - 2.5, bx1 - 4, by1 + cw + 1, frame_top + 1)])  # wire exit
    adds.append(frame)
    body = union([body] + adds)

    cuts = []
    for x, y in d['bosses']:
        cuts.append(cyl(x, y, p['back'] + 1.0, zt + 1, p['boss_hole_d']))
    # USB opening in the bottom wall
    cuts.append(box(d['xc'] - p['usb_w'] / 2, yb - 1, p['usb_z0'], d['xc'] + p['usb_w'] / 2, d['iy0'] + 0.5, p['usb_z1']))
    # GPIB fixing
    gx = p['gpib_dx']
    for gy in (d['gpib_y1'], d['gpib_y2']):
        cuts.append(cyl(gx, gy, -2 - p['key_h'], p['back'] + 1, p['gpib_hole_d']))
        cuts.append(cone(gx, gy, p['back'] - 1.75, p['back'] + 0.01, p['gpib_hole_d'], 6.3))  # countersink M3
    body = cut(body, cuts)
    extra = []
    if p['key']:
        extra.append(rbox(gx - p['key_w'] / 2, d['gpib_yc'] - p['key_len'] / 2, -p['key_h'],
                          gx + p['key_w'] / 2, d['gpib_yc'] + p['key_len'] / 2, 0.01, p['key_w'] / 2 - 0.5))
    if extra:
        body = union([body] + extra)
    return body


def make_lid(p):
    d = derived(p)
    z0, z1 = d['body_top'], p['depth']
    lid = rbox(p['x_left'], d['y_bottom'], z0, p['x_right'], p['y_top'], z1, p['corner_r'])
    cuts = []
    for x, y in d['bosses']:
        cuts.append(cyl(x, y, z0 - 1, z1 + 1, p['lid_hole_d']))
        cuts.append(cone(x, y, z1 - 1.75, z1 + 0.01, p['lid_hole_d'], 6.3))
    if p['vents']:
        # a row of slots over the Wemos and one over the MAX3232
        for yc in (d['wemos_y0'] + 10, 2.0):
            n = int((p['x_right'] - p['x_left'] - 10) // p['vent_pitch'])
            x_start = d['xc'] - (n - 1) * p['vent_pitch'] / 2
            for i in range(n):
                x = x_start + i * p['vent_pitch']
                cuts.append(rbox(x - p['vent_w'] / 2, yc - p['vent_len'] / 2, z0 - 1,
                                 x + p['vent_w'] / 2, yc + p['vent_len'] / 2, z1 + 1, p['vent_w'] / 2 - 0.05))
    lid = cut(lid, cuts)
    # engraving on the outer face, reading along the box
    # two lines between the vent rows, clear of the middle screws
    ty = ((d['wemos_y0'] + 10 + p['vent_len'] / 2) + (2.0 - p['vent_len'] / 2)) / 2
    for txt, size, x in ((p['text_main'], 4.4, d['xc'] - 3.3), (p['text_call'], 4.4, d['xc'] + 3.3)):
        t = text_solid(txt, size, x, ty, z1 - p['text_depth'], p['text_depth'] + 1)
        if t is not None:
            lid = cut(lid, [t])
    return lid


# =====================================================================================
# run
# =====================================================================================
def run_freecad():
    doc = App.newDocument('HydraWemosCase')
    body = doc.addObject('Part::Feature', 'Body')
    body.Shape = make_body(P)
    lid = doc.addObject('Part::Feature', 'Lid')
    lid.Shape = make_lid(P)
    doc.recompute()
    try:
        import FreeCADGui as Gui
        lid.ViewObject.Transparency = 60
        Gui.SendMsgToActiveView('ViewFit')
        Gui.activeDocument().activeView().viewIsometric()
    except Exception:
        pass
    App.Console.PrintMessage('Hydra Wemos case built: Body and Lid. Export them with File → Export (STEP/STL).\n')


def run_cadquery(outdir=None):
    import os
    outdir = outdir or os.path.dirname(os.path.abspath(__file__))
    body, lid = make_body(P), make_lid(P)
    # STL in print orientation: body on its back plate, lid with the outer face on the bed
    cq.exporters.export(cq.Workplane().add(body), os.path.join(outdir, 'hydra_wemos_case_body.stl'),
                        tolerance=0.02, angularTolerance=0.1)
    lid_print = lid.rotate(cq.Vector(0, 0, 0), cq.Vector(1, 0, 0), 180).translate(cq.Vector(0, 0, P['depth']))
    cq.exporters.export(cq.Workplane().add(lid_print), os.path.join(outdir, 'hydra_wemos_case_lid.stl'),
                        tolerance=0.02, angularTolerance=0.1)
    cq.exporters.export(cq.Workplane().add(cq.Compound.makeCompound([body, lid])),
                        os.path.join(outdir, 'hydra_wemos_case.step'))
    print('written to', outdir)
    return body, lid


if BACKEND == 'freecad':
    run_freecad()
elif __name__ == '__main__':
    run_cadquery()
